module toaster-impl {
    yang-version 1;
    namespace "urn:opendaylight:params:xml:ns:yang:toaster:impl";
    prefix "toaster-impl";

    import config { prefix config; revision-date 2013-04-05; }
    import opendaylight-md-sal-binding { prefix md-sal-binding; revision-date 2013-10-28;}
    import rpc-context { prefix rpcx; revision-date 2013-06-17; }

    description
        "Service definition for toaster project";

    revision "2016-03-21" {
        description
            "Initial revision";
    }

    identity toaster {
        base config:module-type;
        config:java-name-prefix Toaster;
    }

    augment "/config:modules/config:module/config:configuration" {
        case toaster {
            when "/config:modules/config:module/config:type = 'toaster'";
                  
            //wires in the data-broker service 
            container data-broker {
                uses config:service-ref {
                    refine type {
                        mandatory false;
                        config:required-identity md-sal-binding:binding-async-data-broker;
                    }
                }
            }
        }
    }
}
